FME workspace town-zug-3d-data-fbx2fgdb.fmw

Parameters:
- DestDataset_GEODATABASE_FILE = $(FME_MF_DIR)town-zug-3d-data.gdb   # File Geodatabase
- SourceDataset_FBX = $(FME_MF_DIR)town-zug-3d-data.fbx   # Source FBX File(s)

Readers:
- FBX_1: FBX from $(SourceDataset_FBX)

Writers:
- GEODATABASE_FILE_1: GEODATABASE_FILE to $(DestDataset_GEODATABASE_FILE)

Note: Read data from fbx
town-zug-3d-data (reader FBX_1)
    -> Scaler
Note: Scale from cm to m: / 0.01
Scaler
    RASTER_SCALING = Extents
    SCALE_ORIGIN = 0,0
    TEXT_LOC_ONLY = Location and Size
    XSCALE = 0.01
    YSCALE = 0.01
    ZSCALE = 0.01
    SCALED -> Offsetter
    <REJECTED> -> Scaler__Rejected_
Note: Offset (LV03): / X 681600 / Y 224500 / Z 0
Offsetter
    MODE = Cartesian Coordinate
    XOFF = 681600
    YOFF = 224500
    ZOFF = 0
    OFFSET -> EsriReprojector
    <REJECTED> -> Offsetter__Rejected_
Note: Reproject: / LV03 --> WGS84 / EPSG: 21781 --> 4326
EsriReprojector
    DEST = ESRIWKT|GCS_WGS_1984|GEOGCS["GCS_WGS_1984",DATUM["D_WGS_1984",SPHEROID["WGS_1984",6378137.0,298.257223563]],PRIMEM["Greenwich",0.0],UNIT["Degree",0.0174532925199433]]
    GEOTRANSFORMATION_DIRECTION = Forward
    GEOTRANSFORMATION_NAME = CH1903_To_WGS_1984_1
    INTERPOLATION_TYPE_NAME = Nearest Neighbor
    RASTER_CELL_SIZE = Preserve Cells
    RASTER_TOLERANCE = 0.0
    SOURCE = ESRIWKT|CH1903_LV03|PROJCS["CH1903_LV03",GEOGCS["GCS_CH1903",DATUM["D_CH1903",SPHEROID["Bessel_1841",6377397.155,299.1528128]],PRIMEM["Greenwich",0.0],UNIT["Degree",0.0174532925199433]],PROJECTION["Hotine_Oblique_Mercator_Azimuth_Center"],PARAMETER["False_Easting",600000.0],PARAMETER["False_Northing",200000.0],PARAMETER["Scale_Factor",1.0],PARAMETER["Azimuth",90.0],PARAMETER["Longitude_Of_Center",7.439583333333333],PARAMETER["Latitude_Of_Center",46.95240555555556],UNIT["Meter",1.0]]
    REPROJECTED -> Deaggregator
Note: Deaggregator to get the attributes / --> Name from the blender object
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AttributeManager
Note: Rename attributes
AttributeManager
    ATTR_TABLE:
      REMOVE _hierarchy_child_id_list{}
      RENAME_SET_VALUE _geometry_name > original_name
      REMOVE _hierarchy_id
      REMOVE _hierarchy_parent_id
      REMOVE _part_number
    -> town_zug_3d_data (writer GEODATABASE_FILE_1)
Note: Write data to fgdb as multipatch
town_zug_3d_data (writer GEODATABASE_FILE_1)
    attributes: original_name char(50)
Offsetter__Rejected_: Inspector [off]
Scaler__Rejected_: Inspector [off]
